module sonic-mobile-management {

    yang-version 1.1;

    namespace "http://github.com/sonic-net/sonic-mobile-management";
    prefix mobile_management;

    import sonic-types {
        prefix stypes;
    }

    description "BLE peripheral daemon configuration for mobile switch management (SwitchMon)";

    revision 2025-06-19 {
        description "First Revision";
    }

    container sonic-mobile-management {

        container MOBILE_MANAGEMENT {

            description "Global mobile-management configuration";

            container GLOBAL {

                leaf state {
                    description "Administrative state of the mobile-management feature";
                    type stypes:admin_mode;
                    default "disabled";
                }

                leaf device_name {
                    description "BLE advertisement device name (max 26 characters)";
                    type string {
                        length "1..26";
                    }
                    default "SwitchMon";
                }

                leaf interval {
                    description "Telemetry notify interval in seconds";
                    type uint16 {
                        range "1..300";
                    }
                    default 2;
                }

                leaf num_ports {
                    description "Number of ports to expose via BLE (max 64)";
                    type uint8 {
                        range "1..64";
                    }
                    default 48;
                }

                leaf session_duration {
                    description "BLE session duration in seconds (0 = unlimited)";
                    type uint32;
                    default 0;
                }

                leaf backend {
                    description "Sensor data backend: sim (simulated) or sonic (real switch data via Redis)";
                    type enumeration {
                        enum sim {
                            description "Simulated sensor data for testing/demos";
                        }
                        enum sonic {
                            description "Real switch telemetry from SONiC Redis databases";
                        }
                        enum auto {
                            description "Use sonic if swsscommon is available, otherwise sim";
                        }
                    }
                    default "auto";
                }

                leaf auth_mode {
                    description "Authentication enforcement mode for BLE control commands";
                    type enumeration {
                        enum enforce {
                            description "Require authentication for write/control commands (default)";
                        }
                        enum bypass {
                            description "Allow full read/write access without authentication";
                        }
                    }
                    default "enforce";
                }
            }
        }

        container MOBILE_MANAGEMENT_AUTH {

            description "Authentication users for BLE mobile-management sessions";

            list MOBILE_MANAGEMENT_AUTH_LIST {
                key "username";

                leaf username {
                    description "Username for HMAC-SHA256 BLE authentication";
                    type string {
                        length "1..64";
                    }
                }

                leaf enabled {
                    description "Whether this auth user is active (password stored out-of-band)";
                    type string {
                        pattern "true|false";
                    }
                    default "true";
                }
            }
        }
    }
}
